NESTED-STATES-ENTRY-EXIT-DATAVIEW DEFINITIONS ::=
BEGIN

   MyInteger ::= INTEGER (0 .. 10000)

   MyStatus ::= ENUMERATED {
       transition-top,
       enter-nested,
       transition-nested,
       leave-nested
   }

END
