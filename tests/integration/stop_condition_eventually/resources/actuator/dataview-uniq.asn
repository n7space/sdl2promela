ENVIRON-TMC-DATAVIEW DEFINITIONS ::=
BEGIN

   Level ::= INTEGER (0 .. 3)

   InternalValue ::= INTEGER(0 .. 2000)

   ResponseStatus ::= BOOLEAN

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END
