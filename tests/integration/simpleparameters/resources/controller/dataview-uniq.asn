MCHECK-DATAVIEW DEFINITIONS ::=
BEGIN
    TestInteger ::= INTEGER (0 .. 10)

    TestParam ::= SEQUENCE {
        valueA TestInteger,
        valueB TestInteger OPTIONAL
    }

    TestX ::= TestParam (WITH COMPONENTS {valueA (0), valueB ABSENT})

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END
