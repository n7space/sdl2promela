Change-observer-Datamodel DEFINITIONS ::=
BEGIN
--  This file was generated automatically by OpenGEODE
IMPORTS
   Actuator-States, Actuator-Context, Actuator-T-Runtime-Error-Selection FROM Actuator-Datamodel
   Controller-States, Controller-Context, Controller-T-Runtime-Error-Selection FROM Controller-Datamodel
   MyInteger, MyTestInteger FROM MULTI-OUTPUT-OBSERVER-DATAVIEW
   T-Int32, T-UInt32, T-Int8, T-UInt8, T-Boolean, T-Null-Record, T-Runtime-Error FROM TASTE-BasicTypes
   PID-Range, PID FROM System-Dataview
   Environ-test-p1 FROM ENVIRON-SUBTYPE
   Actuator-Event, Controller-Event, Environ-Event, Observer-State-Kind, Function-Event, Named-Function-Event, Interface-Event, Create-Event, Delete-Event, Observable-Event, Events-Ty, System-State, System-GUIs FROM Simulation-DataView
   TimerData, AggregateTimerData FROM Simulation-Timers-DataView;

Change-observer-States ::= ENUMERATED {wait}

Change-observer-Context ::= SEQUENCE {
   state Change-observer-States,
   init-done BOOLEAN,
   sender PID,
   offspring PID
}

Change-Observer-T-Runtime-Error-Selection ::= ENUMERATED {noerror-present(1), encodeerror-present(2), decodeerror-present(3)}
Change-Observer-Actuator-Event-Msg-In-Selection ::= ENUMERATED {input-none-present(1), f1-present(2), f2-present(3)}
Change-Observer-Actuator-Event-Msg-Out-Selection ::= ENUMERATED {result-present(1)}
Change-Observer-Actuator-Event-Selection ::= ENUMERATED {msg-in-present(1), msg-out-present(2)}
Change-Observer-Controller-Event-Msg-In-Selection ::= ENUMERATED {input-none-present(1), result-present(2), test-present(3)}
Change-Observer-Controller-Event-Msg-Out-Selection ::= ENUMERATED {f1-present(1), f2-present(2)}
Change-Observer-Controller-Event-Selection ::= ENUMERATED {msg-in-present(1), msg-out-present(2)}
Change-Observer-Environ-Event-Msg-Out-Selection ::= ENUMERATED {test-present(1)}
Change-Observer-Environ-Event-Selection ::= ENUMERATED {msg-out-present(1)}
Change-Observer-Function-Event-Selection ::= ENUMERATED {actuator-present(1), controller-present(2), environ-present(3)}
Change-Observer-Observable-Event-Selection ::= ENUMERATED {no-event-present(1), system-startup-present(2), input-event-present(3), output-event-present(4), unhandled-input-present(5), create-instance-present(6), delete-instance-present(7)}
END
