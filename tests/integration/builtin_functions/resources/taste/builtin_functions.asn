BUILTIN-FUNCTIONS-DATAVIEW DEFINITIONS ::=
BEGIN

   MyInteger ::= INTEGER (0 .. 10000)

   MyBoolean ::= BOOLEAN

   MyArray ::= SEQUENCE (SIZE(1..6)) OF MyInteger

   MyDerivedArray ::= MyArray (SIZE(1..3))

   MyUnion ::= CHOICE {
       speed MyInteger,
       accel MyInteger
   }

   MyEnum ::= ENUMERATED {
       speed,
       accel
   }

   MyStruct ::= SEQUENCE {
       mass MyInteger,
       charge MyInteger OPTIONAL
   }

   MyFixed ::= SEQUENCE (SIZE(2)) OF MyInteger

   MyDerivedFixed ::= MyFixed

END
